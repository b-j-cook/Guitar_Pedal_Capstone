# CapstoneRequirements

## SYS-1: The system shall be capable of accepting user input to define reconfigurable effects for a guitar. (Functional)

### PDL-1: The pedal shall provide user interfaces to alter effects in real time. (Functional)

#### CRL-3: The control pipeline shall accept input from the software application to set effect parameters. (Functional)

#### CRL-4: The control pipeline shall accept input from the software application to define effects. (Functional)

#### CRL-6: The control pipeline shall accept inputs from pedal onboard user interfaces to alter parameters. (Functional)

#### CRL-8: The control pipeline shall provide a stomp activation/deactivation user interface. (Functional)

#### CRL-9: The control pipeline shall provide an indicator for communicating current onboard settings to the user. (Functional)

#### CRL-10: The control pipeline may provide a user interface to switch between guitar and bass guitar impedance matching modes. (Functional)

### PDL-2: The pedal shall be capable of accepting new effect configurations from the accompanying software application. (Functional)

#### CRL-5: The control pipeline shall accept input from the software application to dictate the chain order of effects. (Functional)

### APP-1: The application shall provide deep configurability to digital effects. (Functional)

#### CDP-1: Digital effects shall provide deep configurability to the user. (Functional)

### APP-2: The application shall provide basic tuning parameters for effect components. (Functional)

#### CDP-5: Digital effects shall provide parameter sets. (Functional)

#### CDP-7: The digital effect configuration tool shall provide the capabiliy to alter parameter values. (Functional)

#### CAP-3: The digital effect configuration tool shall provide the capabiliy to alter parameter values. (Functional)

### APP-3: The application shall provide custom algorithm design tools for designing new effects. (Functional)

#### CDP-3: The digital effect configuration tool shall provide users the option to design their own custom algorithms. (Functional)

### APP-4: The application shall be capable of outputting configurations to the pedal. (Functional)

#### CDP-6: The digital effect configuration tool shall allow users to alter digital effect chain path mapping. (Functional)

#### CAP-1: The analog effect configuration tool shall allow users to alter digital effect chain path mapping. (Functional)

#### EVU-6: The effects validation and upload tool shall be capable of uploading effects and effect chain configurations to the pedal. (Functional)

#### EVU-7: Upload to the pedal shall occur upon user upload command. (Functional)

## SYS-2: The system shall be capable of emulating multiple effect blocks on a single input signal. (Functional)

### PDL-3: The pedal shall provide multi-effect chain ordering reconfiguration. (Functional)

#### ASP-5: The analog processing network shall provide the capability to alter analog effect chain mapping. (Functional)

#### CRL-1: The control pipeline shall provide the capability to bypass the DSP board. (Functional)

#### CRL-2: The control pipeline shall provide the capability to bypass analog effects. (Functional)

#### CRL-7: The control pipeline may accept inputs from pedal onboard user interfaces to alter the chain order of effects. (Functional)

#### CRL-11: The control pipeline shall provide the capability to bypass the pre-amp. (Functional)

### PDL-4: The pedal may provide the option to add existing effects pedals to the effects chain. (Functional)

### PDL-22: The pedal shall be capable of processing multiple effects simultaneously. (Functional)

#### DSP-5: The DSP shall be capable of processing multiple simultaneous effects blocks in parallel without exceeding 60% of its available instruction cycles. (Functional)

### APP-5: The application shall provide multi-effect chain reordering configuration. (Functional)

#### EVU-5: The effects validation and upload tool shall prevent users from creating chain mapping combinations not provided by the hardware. (Functional)

### APP-6: The application may be capable of assigning sets of order configurations to be selected on the pedal. (Functional)

## SYS-3: The system's price shall not exceed $300. (Functional)

### PDL-5: The pedal's bill of materials shall not exceed $300. (Functional)

### PDL-6: The pedal shall be open source. (Functional)

### APP-7: The application shall be open source. (Functional)

### APP-8: The application shall not use any third-party software that requires additional monetary investment separate from operating system or other baseline environment requirements. (Functional)

## SYS-4: The system shall be capable of being carried with a single hand. (Functional)

### PDL-8: The pedal shall not exceed a volume of 216in^3. (Functional)

### PDL-9: The pedal's height shall not exceed 4in. (Functional)

## SYS-5: The system's mass shall not exceed 3lbs. (Functional)

### PDL-10: The pedal's mass shall not exceed 3lbs. (Functional)

## SYS-6: The system shall allow users to navigate to the primary features in under a minute. (Functional)

### PDL-11: The pedal shall allow users to alter effects within 5 seconds from the decision to alter to the change being instantiated. (Functional)

#### ASP-1: The analog processing network's settling time shall not exceed 1ms. (Functional)

### PDL-12: The pedal shall inform the user of what effects state they are in. (Functional)

### APP-9: The application shall allow users to navigate to primary tools and effects presets in under a minute. (Functional)

#### CDP-2: Digital effects shall provide multiple levels of abstraction to fit to several user groups. (Functional)

#### CDP-4: The digital effect configuration tool shall allow all users to navigate to primary tools and effect presets in under a minute. (Functional)

#### CAP-2: The analog effect configuration tool shall allow all users to navigate to primary tools and effect presets in under a minute. (Functional)

#### EVU-2: The effects validation and upload tool shall allow users to access validation and upload buttons within 5 seconds. (Functional)

## SYS-7: The system's added total harmonic distortion plus noise shall be less than 0.5%. (Functional)

### PDL-13: The pedal's input impedance shall be at least 10x the instrument pickups' source resistance to minimize pickup loading. (Functional)

#### AFE-1: The impedance-matching network shall result in an input impedance of at least 500kOhms to optimize for the average guitar. (Functional)

#### AFE-2: The impedance-matching network may provide an option to result in an input impedance of at least 100kOhms to optimize for the average bass guitar. (Functional)

#### AFE-3: The impedance-matching network may provide a muxed solution to switch between guitar and bass guitar optimized networks. (Functional)

### PDL-14: The pedal's hardware shall not add more than 0.2% to total harmonic distortion plus noise. (Functional)

#### DSP-1: The DSP board's master clock jitter at the ADC/DAC clock input shall not exceed 100fs RMS. (Functional)

#### DSP-2: The DSP board's ADC shall have a total harmonic distortion that does not exceed -90dB. (Functional)

#### DSP-3: The DSP board's DAC shall have a total harmonic distortion that does not exceed -90dB. (Functional)

#### DSP-4: The DSP board's quantization noise shall not exceed -100dB. (Functional)

#### ASP-2: The analog processing network's clean signal paths shall maintain a frequency response of +/- 5dB from 40Hz to 6kHz. (Functional)

#### ASP-3: The analog processing network shall use switches/relays with R_on less than 10Ohms. (Functional)

#### ASP-4: Crosstalk in the analog processing network between inactive and active effects shall remain less than -100dB within 40Hz to 6kHz. (Functional)

#### EPD-5: Power supply ripple and noise shall not exceed 2mV RMS between 40Hz to 6kHz. (Functional)

### PDL-23: The pedal shall use anti-aliasing filters will be used to keep aliasing products at least 60-80dB below that of the fundamental. (Functional)

### APP-10: The application shall warn, disable with warning, or modify with warning, any effect that would cause total harmonic distortion plus noise to increase by 0.5%. (Functional)

#### EVU-1: The efffects validation and upload tool shall warn, disable with warning, or modify with warning, any effect that would cause total harmonic distortion plus noise to increase by 0.3%. (Functional)

#### EVU-3: The effects validation and upload tool shall provide users selectable options for effect warning level. (Functional)

#### EVU-4: The effects validation and upload tool shall throw a warning for chain mapping sets that may cause total harmonic distortion plus noise to increase by 0.1% as order of non-linear effects matter. (Functional)

## SYS-8: The system's latency from input to output shall not exceed 5ms. (Functional)

### PDL-15: The pedal's latency shall not exceed 5ms from input to output. (Functional)

## SYS-9: The system shall integrate with both the instrument and the output sound system. (Functional)

### PDL-16: The pedal shall integrate with the instrument. (Functional)

#### AFE-4: The pedal shall provide a 1/4 inch TS input port. (Functional)

### PDL-17: The pedal shall integrate with a guitar/bass amplifier. (Functional)

#### OUD-1: The pedal shall provide a 1/4 inch TS output port. (Functional)

### PDL-18: The pedal may integrate with a PA system. (Functional)

#### OUD-3: The pedal may provide a XLR output port. (Functional)

#### OUD-5: The pedal may provide a preamp for improved output performance. (Functional)

#### OUD-7: The preamp may drive 1/4 inch TS, XLR, and 1/8 inch outputs. (Functional)

### PDL-19: The pedal may integrate with a computer setup. (Functional)

#### OUD-2: The pedal may provide a USB-MIDI output port. (Functional)

#### OUD-6: USB-MIDI output driver may deliver messages without loss or corruption. (Functional)

### PDL-20: The pedal may integrate with a corded headset. (Functional)

#### OUD-4: The pedal may provide a 1/8 inch audio output port. (Functional)

## SYS-10: The system shall be powered from a 9V power supply. (Functional)

### PDL-21: The pedal shall be powered from a 9V power supply. (Functional)

#### EPD-1: The electronics power distribution shall use a 9V power source. (Functional)

#### EPD-2: The electronics power distribution shall not require more than 500mA. (Functional)

#### EPD-3: The electronics power distribution unit shall provide power to all necessary components during use. (Functional)

#### EPD-4: The electronics power distribution shall have central-positive or central-negative polarity. (Functional)

## SYS-11: The system shall provide a materials usage package. (Functional)

### PDL-7: The pedal shall not require additional information to assemble than what is provided in the materials usage package. (Functional)

### APP-11: The application shall provide elementary tutorials on how to design/alter effects. (Functional)

## SYS-12: The system shall be capable of performing reliably for over an hour continuously. (Functional)

### PDL-24: The pedal shall regulate its internal temperature to ensure all processing units operate at or below 80% of their rated thermal capacity under typical usage conditions. (Functional)

## I-DSP-1: Image of ElectroSmith board. (Functional)
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